Sub CATMain()
	Dim mycatia As Application
	Set mycatia = CATIA	

	Dim mydocs As Documents
 	Set mydocs = CATIA.Documents
	
	Dim mydocument As Document
 	Set mydocument = mydocs.Add("CATPart")

End Sub
