Sub CATMain()
	Dim DName As CATBSTR
	Dim Box
	DName = CATIA.ActiveDocument.FullName
Box = MsgBox("fullname is:" & Chr(34) & DName & Chr(34) & ".", 64) 
CATIA.ActiveDocument.Save()
CATIA.ActiveDocument.Close()
	
End Sub
