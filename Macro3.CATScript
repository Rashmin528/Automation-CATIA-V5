Sub Main()
	Dim mycatia As Application
	Set mycatia = CATIA
	
	Dim mydoc As Document
	Set mydoc = CATIA.ActiveDocument
	
	Dim MyProduct As Product
	Set MyProduct  = CATIA.ActiveDocument.Product
	
	Dim BAttrib As Parameters
	Set BAttrib = CATIA.ActiveDocument.Product.UserRefProperties
	
	Dim mybool As BoolParam
	Set mybool = BAttrib.CreateBoolean("StandardPart", True)
End Sub
