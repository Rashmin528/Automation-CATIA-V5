Sub CATMain()
	Dim mycatia As Application
	Set mycatia = CATIA
	
	Dim mydoc As Document
	Set mydoc = CATIA.ActiveDocument
	
	Dim MyDocument As Part
	Set MyDocument  = CATIA.ActiveDocument.Part
	
	Dim myOrigin
	Set myplane =  MyDocument.OriginElements
	
	Dim myP
	Set myP = myplane.PlaneYZ

End Sub
